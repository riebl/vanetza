-- ############################################################################
-- ############################################################################
--
-- This is the ASN.1 definition used in the J2735 ballot of Nov 04th 2014.
-- It includes the messages SPAT, MapData and the related data frames and
-- data elements for usage within European region.
-- 
-- The definiton of the ASN.1 included in this document is identified by 
-- the Version: 1.0.
-- The element "msgSubID" in the messages MapData and SPAT are used for
-- identification of the ASN.1 definition for Region D (e.g. Europe) and are
-- set to the integer value = 1.
-- 
-- The data elements of the messages SPAT and MapData are harmonized  
-- with the data elements from the data dictionary ETSI TS 102 894-2 V1.1.15.
--
-- The message set for SPAT and MapData has been harmonized for usage in
-- diffrerent international regions. Some data elements include regional
-- enhancements. If no enhancement is defined, the regional ASN.1 extension
-- points to an empty data element of the Module "REGION".
-- If regional enhancements are defined the regional ASN.1 extension points
-- to a data element of the specific region. For Europe the ASN.1 extensions
-- are defined in the module REG-D.

-- ############################################################################
-- ############################################################################



-- ############################################################################
-- ^-^-^-^-^-^-^-^-^-^-^-^-^-^-^-^-^-^-^-^-^-^-^-^-^-^-^-^-^-^-^-^-^-^-^-^-^-^-
-- 
-- Begin module: DSRC
-- 
-- ^-^-^-^-^-^-^-^-^-^-^-^-^-^-^-^-^-^-^-^-^-^-^-^-^-^-^-^-^-^-^-^-^-^-^-^-^-^-
-- ############################################################################
DSRC {
  iso (1) standard (0) signalizedIntersection (19091) profilec(2) dsrc (2) version2 (2)
}

DEFINITIONS AUTOMATIC TAGS::= BEGIN
 
-- =============================================================================
-- 
-- Imports from Modules:
-- ITS-Container: ETSI common Data Dictionary
-- REGION:        Generic or empty regional data elements.
-- RED_D:         Region D extension (e.g Europe).
-- 
-- =============================================================================
 
IMPORTS
	Latitude, Longitude, SpeedConfidence
    FROM ITS-Container { itu-t (0) identified-organization (4) etsi (0) itsDomain (5) wg1 (1) ts (102894) cdd (2) version (2) }

	Reg-AdvisorySpeed,Reg-ComputedLane, Reg-GenericLane, Reg-Intersection,
	Reg-LaneAttributes, Reg-LaneDataAttribute,
	Reg-MovementEvent, Reg-MovementState, Reg-NodeAttribute,
 	Reg-NodeOffsetPoint, Reg-RoadSegment, Reg-SignalControlZone, Reg-SPAT
	FROM REGION

	Reg-MapData, Reg-ConnectionManeuverAssist, Reg-IntersectionState,
	Reg-Position3D, Reg-RestrictionUserType
	FROM REG-D;

	
-- =============================================================================
-- MSG_MapData  (MAP) (Desc Name) Record 6
--
-- Region D: different usage of the following elements within Europe:
--
-- msgSubID: Set to integer 1 for identification of this actual ASN.1 definition
--  of the MapData message.
--
-- layerType: Based on the value of the "LayerType" the topological description
--  for "intersection" or "roadSegments" is used. The usage of both
--  "intersection" and "roadSegments" are not forseen in Europe.
--
-- msgIssueRevision: Not used in Region D (e.g. Europe)
--
-- layerID: Used for logical fragmentation of MapData
--
-- dataParameters: Not used in Region D (e.g. Europe)
--
-- crc: not used in Region D (e.g. in Europe)
--
MapData ::=  SEQUENCE {
   msgID             DSRCmsgID2,      
   
   msgSubID          DSRCmsgSubID OPTIONAL, 
				     -- Region D: Version of ASN.1 definition 
					 
   msgIssueRevision  MsgCount,
  					 -- Region D: msgIssueRevision
 					 --  is not used Region D (e.g. Europe)
					 
   layerType         LayerType OPTIONAL,
   
   layerID           LayerID  OPTIONAL,
   
   intersections     IntersectionGeometryList OPTIONAL,
                     -- All Intersection definitions 
   
   -- NOTE:
   -- other map data will be added here as it is defined
   -- (curve warnings, construction routes, etc.)
   -- as an example of this:
   roadSegments      RoadSegmentList OPTIONAL,
                     -- All roadway descriptions
  
   dataParameters    DataParameters OPTIONAL,
  					 -- Region D: dataParameters
 					 --  is not used in Region D (e.g. Europe)
					 
   restrictionList   RestrictionClassList OPTIONAL,
                     -- Any restriction ID tables which have  
                     -- established for these map entries.
					 
   regional          RegionalMapData OPTIONAL, 
                     -- regional extensions.
					 
   crc               MsgCRC OPTIONAL,
  					 -- Region D: crc
 					 --  is not used in Region D (e.g. Europe)
   ... -- # LOCAL_CONTENT
   }

   
-- =============================================================================
-- MSG_SignalPhaseAndTiming Message  (SPAT) (Desc Name) Record 14
--
-- Region D: different usage of the following elements within Europe:
--
-- msgSubID: Set to integer 1 for identification of this actual ASN.1 definition
--  of the SPAT message.
--
SPAT ::=  SEQUENCE { 
   msgID         DSRCmsgID2,      
   msgSubID      DSRCmsgSubID OPTIONAL,
				 -- Region D: Version of ASN.1 definition 
				 
   name          DescriptiveName OPTIONAL, 
                 -- human readable name for this collection 
                 -- to be used only in debug mode
   
   intersections IntersectionStateList,
                 -- sets of SPAT data (one per intersection)  
   
   -- If PrioritizationResponse data is required, it is found 
   -- in the RegionalSPAT entry below
   
   regional     RegionalSPAT OPTIONAL, -- regional extensions
   ... -- # LOCAL_CONTENT
   }

   
-- -_-_-_-_-_-_-_-_-_-_-_-_-_-_-_-_-_-_-_-_-_-_-_-_-_-_-_-_-_-_-_-_-_-_-_-_-_-_
-- 
-- Start of entries from table Data_Frames...
-- This table contains data frame entries.
-- -_-_-_-_-_-_-_-_-_-_-_-_-_-_-_-_-_-_-_-_-_-_-_-_-_-_-_-_-_-_-_-_-_-_-_-_-_-_

-- ============================================================================
-- DF_AdvisorySpeed (Desc Name) Record 3
AdvisorySpeed ::=  SEQUENCE {
   type        AdvisorySpeedType,
               -- the type of advisory which this is.
			   
   speed       SpeedAdvice OPTIONAL,
               -- See Remarks under the SpeedAdvice entry for
               -- converting and transmitting a speed expressed
               -- in MPH to units of 0.1 m/s
               -- This element is optional ONLY when superceded 
               -- by the presence of a regional speed element found in
               -- RegionalAdvisorySpeed
			   
   confidence  SpeedConfidence OPTIONAL,
               -- A confidence value for the above speed
			   
   distance    ZoneLength OPTIONAL,
               -- Unit = 1 meter,  
               -- The distance indicates the region for which the advised speed 
               -- is recommended, it is specified upstream from the stop bar  
               -- along the connected egressing lane
			   
   class       RestrictionClassID OPTIONAL,
               -- the vehicle types to which it applies
               -- when absent, the AdvisorySpeed applies to
               -- all motor vehicle types
			   
   regional    RegionalAdvisorySpeed OPTIONAL,
               -- regional extensions
   ...
   }

   
-- =============================================================================
-- DF_AdvisorySpeedList (Desc Name) Record 4
AdvisorySpeedList ::=  SEQUENCE (SIZE(1..16)) OF AdvisorySpeed

 
-- =============================================================================
-- DF_ComputedLane CHANGED (Desc Name) Record 10
ComputedLane ::=  SEQUENCE {
   -- Data needed to created a computed lane
   referenceLaneId    LaneID,
                         -- the lane ID upon which this 
                         -- computed lane will be based 
						 
   -- Lane Offset in X and Y direction
   offsetXaxis        CHOICE {
                         small   DrivenLineOffsetSm, 
                         large   DrivenLineOffsetLg
                         },  
   offsetYaxis        CHOICE {
                         small   DrivenLineOffsetSm, 
                         large   DrivenLineOffsetLg
                         },  
                         -- An path X offset value for translations of the 
                         -- path's points when created translated lanes. 
                         -- The values found in the reference lane are 
                         -- all offset based on the X and Y values from 
                         -- the coordinates of the reference lane's 
                         -- starting initial point.   
   -- Lane Rotation
   rotateXY           Angle OPTIONAL, 
                         -- A path rotation value for the entire lane
                         -- Observe that this rotates the existing orientation 
                         -- of the referenced lane, it does not replace it.
						 
   -- Lane Path Scale (zooming)
   scaleXaxis         Scale-B12 OPTIONAL, 
   scaleYaxis         Scale-B12 OPTIONAL, 
                         -- value for translations or zooming of the path's 
                         -- points. The values found in the reference lane 
                         -- are all expanded of contracted based on the X 
                         -- and Y and width values from the coordinates of 
                         -- the reference lane's starting initial point.  
                         -- The Z axis remains untouched.  
   regional           RegionalComputedLane OPTIONAL, 
                      -- regional extensions
   ... 
   }

   
-- =============================================================================
-- DF_ConnectingLane (Desc Name) Record 12
ConnectingLane ::=  SEQUENCE {
   lane      LaneID,   -- Index of the connecting lane
   maneuver  AllowedManeuvers OPTIONAL
                       -- Region D: Not Used in Europe
                       -- The information within "maneuver" is not precise
                       -- Use "connectsTo" for maneuver description
   }

   
-- =============================================================================
-- DF_Connection (Desc Name) Record 13
Connection ::=  SEQUENCE {
   -- The subject lane connecting to this lane is:
   connectingLane     ConnectingLane, 
                      -- The index of the connecting lane and also
                      -- the maneuver from the current lane to it
					  
   remoteIntersection IntersectionReferenceID OPTIONAL,  
                      -- This entry is only used when the 
                      -- indicated connecting lane belongs 
                      -- to another intersection layout. This 
                      -- provides a means to create meshes of lanes
   
   -- SPAT mapping details at the stop line are:
   signalGroup        SignalGroupID OPTIONAL,    
                      -- The matching signal group send by 
                      -- the SPAT message for this lane/maneuver
                      -- Shall be present unless the connectingLane 
                      -- has not signal group (is un-signalized)
					  
   userClass          RestrictionClassID OPTIONAL, 
                      -- The Restriction Class of users this applies to
                      -- The use of some lane/maneuver and SignalGroupID 
                      -- pairings are restricted to selected users
                      -- when absent, the SignalGroupID applies to all
   
   -- Movement assist details are given by:
   connectionID       LaneConnectionID OPTIONAL
                      -- An optional connection index used to 
                      -- relate this lane connection to any dynamic 
                      -- clearance data in the SPAT. Note that
                      -- the index may be shared with other 
                      -- connections if the clearance data is common
   }

   
-- =============================================================================
-- DF_ConnectionManeuverAssist (Desc Name) Record 14
ConnectionManeuverAssist ::=  SEQUENCE {
   connectionID         LaneConnectionID,
                        -- the common connectionID used by all lanes to which
                        -- this data applies 
                        -- (this value traces to ConnectsTo entries in lanes)
						
   -- Expected Clearance Information
   queueLength          ZoneLength OPTIONAL,
                        -- Unit = 1 meter, 0 = no queue
                        -- The distance from the stop line to the back 
                        -- edge of the last vehicle in the queue,                     
                        -- as measured along the lane center line.
						
   availableStorageLength ZoneLength OPTIONAL,
                        -- Unit = 1 meter, 0 = no space remains
                        -- Distance (e.g. beginning from the downstream 
                        -- stop-line up to a given distance) with a high 
                        -- probability for successfully executing the 
                        -- connection maneuver between the two lanes 
                        -- during the current cycle. 
                        -- Used for enhancing the awareness of vehicles 
                        -- to anticipate if they can pass the stop line
                        -- of the lane. Used for optimizing the green wave, 
                        -- due to knowledge of vehicles waiting in front 
                        -- of a red light (downstream).
                        -- The element nextTime in TimeChangeDetails
                        -- in the containing data frame contains the next 
                        -- timemark at which an active phase is expected, 
                        -- a form of storage flush interval.
						
   waitOnStop           WaitOnStopline OPTIONAL,
                        -- If "true", the vehicles on this specific connecting 
                        -- maneuver have to stop on the stop-line and not 
                        -- to enter the collision area 
						
   pedBicycleDetect     PedestrianBicycleDetect OPTIONAL,
                        -- true if ANY ped or bicycles are detected crossing 
                        -- the above lanes. Set to false ONLY if there is a 
                        -- high certainty that there are none present, 
                        -- otherwise element is not sent.
						
   regional             RegionalConnectionManeuverAssist OPTIONAL, 
                        -- regional extensions
   ... -- # LOCAL_CONTENT
   }

   
-- =============================================================================
-- DF_ConnectsToList (Desc Name) Record 15
ConnectsToList ::=  SEQUENCE (SIZE(1..16)) OF Connection

 
-- =============================================================================
-- DF_DataParameters (Desc Name) Record 16
DataParameters ::=  SEQUENCE {
   processMethod     IA5String(SIZE(1..255)) OPTIONAL, 
   processAgency     IA5String(SIZE(1..255)) OPTIONAL, 
   lastCheckedDate   IA5String(SIZE(1..255)) OPTIONAL, 
   geoidUsed         IA5String(SIZE(1..255)) OPTIONAL, 
   ... -- # LOCAL_CONTENT
   }

   
-- =============================================================================
-- DF_EnabledLaneList (Desc Name) Record 23
EnabledLaneList ::=  SEQUENCE (SIZE(1..16)) OF LaneID
   -- The unique ID numbers for each
   -- lane object which is 'active' 
   -- as part of the dynamic map contents.

   
-- =============================================================================
-- DF_GenericLane  CHANGED (Desc Name) Record 26
GenericLane ::=  SEQUENCE { 

   laneID           LaneID, 
                    -- The unique ID number assigned 
                    -- to this lane object
					
   name             DescriptiveName OPTIONAL,        
                    -- often for debug use only 
                    -- but at times used to name ped crossings
					
   ingressApproach  ApproachID OPTIONAL, -- inbound
   egressApproach   ApproachID OPTIONAL, -- outbound
                    -- Approach IDs to which this lane belongs

   laneAttributes   LaneAttributes, 
                    -- All Attribute information about 
                    -- the basic selected lane type
                    -- Directions of use, Geometric co-sharing
                    -- and Type Specific Attributes
                    -- These Attributes are 'lane - global' that is,
                    -- they are true for the entire length of the lane
					
   maneuvers        AllowedManeuvers OPTIONAL,
					-- Region D: Not used e.g. in Europe!
					-- The information within "maneuvers" is not precise
					-- Use the "connectsTo" element for maneuver direction description

   nodeList         NodeList2,
                    -- Lane spatial path information as well as
                    -- various Attribute information along the node path  
                    -- Attributes found here are more general and may
                    -- come and go over the length of the lane.
					
   connectsTo       ConnectsToList OPTIONAL, 
                    -- a list of other lanes and their signal group IDs
                    -- each connecting lane and its signal group ID
                    -- is given, therefore this element provides the
                    -- information formally in "signalGroups" in prior
                    -- editions.
					
   overlays         OverlayLaneList OPTIONAL, 
                    -- A list of any lanes which have spatial paths that
                    -- overlay (run on top of, and not simply cross) 
                    -- the path of this lane when used
					
   regional         RegionalGenericLane OPTIONAL, 
                    -- regional extensions
   ... 
   }

   
-- =============================================================================
-- DF_IntersectionGeometry CHANGED (Desc Name) Record 28
IntersectionGeometry ::=  SEQUENCE {
   name        DescriptiveName OPTIONAL, 
                            -- For debug use only
   id          IntersectionReferenceID,  
                            -- A globally unique value set, 
                            -- consisting of a regionID and 
                            -- intersection ID assignment
   revision    MsgCount, 
                -- Region D: 
				-- The actual valid revision of the intersection geometry.
				-- The revision Remains the if geometry is not changed.
				-- The revision of the geometry is related to the revision of
				--  the intersection state (see "DF_IntersectionState").
				
   -- Required default values about lane descriptions follow
   refPoint    Position3D-2, -- The reference from which subsequent 
                            -- data points are offset until a new
                            -- point is used. 
							
   laneWidth   LaneWidth OPTIONAL,   
                            -- Reference width used by all subsequent 
                            -- lanes unless a new width is given.  
							
   speedLimits SpeedLimitList OPTIONAL, 
                            -- Reference regulatory speed limits
                            -- used by all subsequent 
                            -- lanes unless a new speed is given 
                            -- See Remarks under the SpeedAdvice entry 
                            -- for converting and transmitting a speed 
                            -- expressed in MPH to units of 0.1 m/s

   -- Complete details regarding each lane type in this intersection
   laneSet     LaneList,    -- Data about one or more lanes
                            -- (all lane data is found here)
							
   preemptPriorityData PreemptPriorityList OPTIONAL, 
							-- Region D: preemptPriorityData
 							--  is not used in Region D (e.g. Europe)
							
   regional    RegionalIntersection  OPTIONAL,
               -- regional message content to be placed here
   ... 
   }

   
-- =============================================================================
-- DF_IntersectionGeometryList (Desc Name) Record 29
IntersectionGeometryList ::=  SEQUENCE (SIZE(1..32)) OF IntersectionGeometry

 
-- =============================================================================
-- DF_IntersectionReferenceID  CHANGED (Desc Name) Record 30
IntersectionReferenceID ::=  SEQUENCE {
   region  RoadRegulatorID OPTIONAL,
           -- a globally unique regional assignment value
           -- typical assigned to a regional DOT authority
           -- the value zero shall be used for testing needs
		   
   id      IntersectionID
           -- a unique mapping to the intersection
           -- in question within the above region of use
   }

   
-- =============================================================================
-- DF_IntersectionState CHANGED (Desc Name) Record 31
IntersectionState ::=  SEQUENCE {
   name         DescriptiveName OPTIONAL, 
                -- human readable name for intersection  
                -- to be used only in debug mode.
				
   id           IntersectionReferenceID,  
                -- A globally unique value set, consisting of a 
                -- regionID and intersection ID assignment
                -- provides a unique mapping to the 
                -- intersection MAP in question
                -- which provides complete location 
                -- and approach/move/lane data
				
   revision     MsgCount,    
   
   status       IntersectionStatusObject,
                -- general status of the controller(s)
				
   moy          MinuteOfTheYear OPTIONAL,
                -- Minute of current UTC year
                -- used only with messages to be archived 
				
   timeStamp    DSecond2 OPTIONAL, 
                -- the mSec point in the current UTC minute that
                -- this message was constructed
				
   enabledLanes EnabledLaneList OPTIONAL,  
                -- a list of lanes where the RevocableLane bit 
                -- has been set which are now active and 
                -- therefore part of the current intersection
				
   states       MovementList,
                -- Each Movement is given in turn
                -- and contains its signal phase state, 
                -- mapping to the lanes it applies to, and
                -- point in time it will end, and it
                -- may contain both active and future states 
				
   maneuverAssistList  ManeuverAssistList OPTIONAL,
                -- Assist data
				
   priority     SignalControlState OPTIONAL,
                -- the active priority state data, if present
				
   preempt      SignalControlState OPTIONAL,
                -- the active preemption state data, if present
   
   regional     RegionalIntersectionState OPTIONAL, 
                -- regional extensions   
   ... 
   }

   
-- =============================================================================
-- DF_IntersectionStateList (Desc Name) Record 32
IntersectionStateList ::=  SEQUENCE (SIZE(1..32)) OF  IntersectionState

 
-- =============================================================================
-- DF_LaneAttributes (Desc Name) Record 34
LaneAttributes ::=  SEQUENCE {
   directionalUse  LaneDirection,      -- directions of lane use
   sharedWith      LaneSharing,        -- co-users of the lane path
   laneType        LaneTypeAttributes, -- specific lane type data
   regional        RegionalLaneAttributes OPTIONAL 
                                       -- regional extensions
   }

   
-- =============================================================================
-- DF_LaneDataAttribute (Desc Name) Record 35
LaneDataAttribute ::=  CHOICE {
    -- Segment attribute types and the data needed for each
    pathEndPointAngle        DeltaAngle,  
                             -- adjusts final point/width slant
                             -- of the lane to align with the stop line.
							 
    laneCrownPointCenter     RoadwayCrownAngle,  
                             -- sets the canter of the road bed      
                             -- from centerline point.
							 
    laneCrownPointLeft       RoadwayCrownAngle,  
                             -- sets the canter of the road bed
                             -- from left edge.
							 
    laneCrownPointRight      RoadwayCrownAngle,  
                             -- sets the canter of the road bed
                             -- from right edge.
							 
    laneAngle                MergeDivergeNodeAngle,  
                             -- the angle or direction of another lane
                             -- this is required to support Japan style
                             -- when a merge point angle is required.
							 
    speedLimits              SpeedLimitList,
                             -- Reference regulatory speed limits
                             -- used by all segments.
							    
    -- Add others as needed, here or in regional space
    regional                 RegionalLaneDataAttribute,
                             -- regional extensions
    ...
    }

	
-- =============================================================================
-- DF_LaneDataAttributeList (Desc Name) Record 36
LaneDataAttributeList ::=  SEQUENCE (SIZE(1..8)) OF LaneDataAttribute

 
-- =============================================================================
-- DF_LaneList (Desc Name) Record 37
LaneList ::=  SEQUENCE (SIZE(1..255)) OF GenericLane

 
-- =============================================================================
-- DF_LaneTypeAttributes (Desc Name) Record 38
LaneTypeAttributes ::=  CHOICE {
   vehicle        LaneAttributes-Vehicle,        -- motor vehicle lanes
   crosswalk      LaneAttributes-Crosswalk,      -- pedestrian crosswalks
   bikeLane       LaneAttributes-Bike,           -- bike lanes
   sidewalk       LaneAttributes-Sidewalk,       -- pedestrian sidewalk paths
   median         LaneAttributes-Barrier,        -- medians & channelization
   striping       LaneAttributes-Striping,       -- roadway markings
   trackedVehicle LaneAttributes-TrackedVehicle, -- trains and trolleys
   parking        LaneAttributes-Parking,        -- parking and stopping lanes
   ...
   }

   
-- =============================================================================
-- DF_ManeuverAssistList (Desc Name) Record 39
ManeuverAssistList ::=  SEQUENCE (SIZE(1..16)) OF ConnectionManeuverAssist

 
-- =============================================================================
-- DF_MovementEvent CHANGED (Desc Name) Record 40
MovementEvent ::=  SEQUENCE {
   eventState   MovementPhaseState,
                -- Consisting of:
                -- Phase state (the basic 11 states)
                -- Directional, protected, or permissive state
   
   timing       TimeChangeDetails OPTIONAL,
                -- Timing Data in UTC time stamps for event
                -- includes start and min/max end times of phase
                -- confidence and estimated next occurrence
   
   speeds       AdvisorySpeedList OPTIONAL,
                -- various speed advisories for use by
                -- general and specific types of vehicles
                -- supporting green-wave and other flow needs
                -- See Remarks under the SpeedAdvice entry for
                -- converting and transmitting a speed expressed
                -- in MPH to units of 0.1 m/s
   
   regional     RegionalMovementEvent OPTIONAL, 
                -- regional extensions
   ... -- # LOCAL_CONTENT
   }

   
-- =============================================================================
-- DF_MovementEventList (Desc Name) Record 41
MovementEventList ::=  SEQUENCE (SIZE(1..16)) OF MovementEvent

 
-- =============================================================================
-- DF_MovementList (Desc Name) Record 42
MovementList ::=  SEQUENCE (SIZE(1..255)) OF MovementState

 
-- =============================================================================
-- DF_MovementState (Desc Name) Record 43
MovementState ::=  SEQUENCE {
   movementName       DescriptiveName OPTIONAL,
                      -- uniquely defines movement by name   
                      -- human readable name for intersection  
                      -- to be used only in debug mode.
					  
   signalGroup        SignalGroupID,    
                      -- the group id is used to map to lists 
                      -- of lanes (and their descriptions) 
                      -- which this MovementState data applies to 
                      -- see comments in the Remarks for usage details 
					  
   state-time-speed   MovementEventList,   
                      -- Consisting of sets of movement data with:
                      -- a)  SignalPhaseState
                      -- b)  TimeChangeDetails,  and 
                      -- c)  AdvisorySpeeds      (optional )
                      -- Note one or more of the movement events may be for 
                      -- a future time and that this allows conveying multiple 
                      -- predictive phase and movement timing for various uses
                      -- for the current signal group.
					  
   maneuverAssistList ManeuverAssistList OPTIONAL,
                      -- This information may also be placed in the 
                      -- IntersectionState when common information applies to
                      -- different lanes in the same way.
					  
   regional           RegionalMovementState OPTIONAL, 
                      -- regional extensions
   ... -- # LOCAL_CONTENT
   }

   
-- =============================================================================
-- DF_Node (Desc Name) Record 44
Node ::=  SEQUENCE {
   delta       NodeOffsetPoint,
               -- A choice of which X,Y offset value to use  
               -- this includes various delta values as well a regional choices.
			   
   attributes  NodeAttributeSet OPTIONAL,
               -- Any optional Attributes which are needed
               -- This includes changes to the current lane width and elevation
   ... 
   }

   
-- =============================================================================
-- DF_NodeAttributeList (Desc Name) Record 45
NodeAttributeList ::=  SEQUENCE (SIZE(1..8)) OF NodeAttribute

 
-- =============================================================================
-- DF_NodeAttributeSet (Desc Name) Record 46
NodeAttributeSet ::=  SEQUENCE {
   localNode    NodeAttributeList OPTIONAL,
                -- Attribute states which pertain to this node point.
				
   disabled     SegmentAttributeList OPTIONAL,
                -- Attribute states which are disabled at this node point.
				
   enabled      SegmentAttributeList OPTIONAL,
                -- Attribute states which are enabled at this node point
                -- and which remain enabled until disabled or the lane ends.
				
   data         LaneDataAttributeList OPTIONAL,
                -- Attributes which require an additional data values
                -- some of these are local to the node point, while others
                -- persist with the provided values until changed
                -- and this is indicated in each entry.
				
   regional     RegionalNodeAttributeList OPTIONAL, 
                -- Regional extensions.
				
   dWidth       Offset-B10 OPTIONAL,
                -- A value added to the current lane width
                -- at this node and from this node onwards, in 1cm steps
                -- lane width between nodes are a linear taper between pts
                -- the value of zero shall not be sent here.
				
   dElevation   Offset-B10 OPTIONAL,
                -- A value added to the current Elevation 
                -- at this node from this node onwards, in 10cm steps
                -- elevations between nodes are a linear taper between pts
                -- the value of zero shall not be sent here
   ...
   }

   
-- =============================================================================
-- DF_NodeList2 CHANGED (Desc Name) Record 48
NodeList2 ::=  CHOICE {
   nodes     NodeSet,
             -- a lane made up of two or more
             -- node points and any attributes 
             -- defined in those nodes.

   computed  ComputedLane,
             -- a lane path computed by translating 
             -- the data defined by another lane.
   ...
   }

   
-- =============================================================================
-- DF_Node_LLmD_64b (Desc Name) Record 49
Node-LLmD-64b ::=  SEQUENCE {
   lon  Longitude,
   lat  Latitude
   }

   
-- =============================================================================
-- DF_NodeOffsetPoint (Desc Name) Record 50
NodeOffsetPoint ::=  CHOICE {
   -- Nodes with X,Y content
   node-XY1         Node-XY-20b,    -- node is within   5.11m of last node
   node-XY2         Node-XY-22b,    -- node is within  10.23m of last node
   node-XY3         Node-XY-24b,    -- node is within  20.47m of last node
   node-XY4         Node-XY-26b,    -- node is within  40.96m of last node
   node-XY5         Node-XY-28b,    -- node is within  81.91m of last node
   node-XY6         Node-XY-32b,    -- node is within 327.67m of last node
   node-LatLon      Node-LLmD-64b,  -- node is a full 32b Lat/Lon range
   node-Regional    RegionalNodeOffsetPoint
                                    -- node which follows is of a 
                                    -- regional definition type 
   }

   
-- =============================================================================
-- DF_NodeSet (Desc Name) Record 51
NodeSet ::=  SEQUENCE (SIZE(2..63)) OF Node

 
-- =============================================================================
-- DF_Node_XY_20b (Desc Name) Record 52
Node-XY-20b ::=  SEQUENCE {
   x  Offset-B10,
   y  Offset-B10
   }

   
-- =============================================================================
-- DF_Node_XY_22b (Desc Name) Record 53
Node-XY-22b ::=  SEQUENCE {
   x  Offset-B11,
   y  Offset-B11
   }

   
-- =============================================================================
-- DF_Node_XY_24b (Desc Name) Record 54
Node-XY-24b ::=  SEQUENCE {
   x  Offset-B12,
   y  Offset-B12
   }

   
-- =============================================================================
-- DF_Node_XY_26b (Desc Name) Record 55
Node-XY-26b ::=  SEQUENCE {
   x  Offset-B13,
   y  Offset-B13
   }

   
-- =============================================================================
-- DF_Node_XY_28b (Desc Name) Record 56
Node-XY-28b ::=  SEQUENCE {
   x  Offset-B14,
   y  Offset-B14
   }

   
-- =============================================================================
-- DF_Node_XY_32b (Desc Name) Record 57
Node-XY-32b ::=  SEQUENCE {
   x  Offset-B16,
   y  Offset-B16
   }

   
-- =============================================================================
-- DF_OverlayLaneList (Desc Name) Record 59
OverlayLaneList ::=  SEQUENCE (SIZE(1..5)) OF LaneID
   -- The unique ID numbers for any lane object which have
   -- spatial paths that overlay (run on top of, and not
   -- simply cross with) the current lane.
   -- Such as a train path that overlays a motor vehicle
   -- lane object for a roadway segment.

   
-- =============================================================================
-- DF_Position3D_2 CHANGED (Desc Name) Record 73
Position3D-2 ::=  SEQUENCE {
   lat        Latitude,                -- in 1/10th micro degrees
   long       Longitude,               -- in 1/10th micro degrees
   
   elevation  Elevation2 OPTIONAL,
                    -- Region D: Not used e.g. in Europe!
                    -- For compatibility with the European Data Dictionary 
                    -- please use the RegionalPosition3D for Europe

   regional   RegionalPosition3D OPTIONAL,
                    -- Region D:
                    -- Elevation is coded based on ETSI CDD definition
					-- and defined in the european Module. 
   ...
   }

   
-- =============================================================================
-- DF_PreemptPriorityList (Desc Name) Record 76
PreemptPriorityList ::=  SEQUENCE (SIZE(1..32)) OF RegionalSignalControlZone
 
-- =============================================================================
-- DF_Regional_AdvisorySpeed (Desc Name) Record 77
RegionalAdvisorySpeed ::=  Reg-AdvisorySpeed 
 
-- =============================================================================
-- DF_Regional_ComputedLane (Desc Name) Record 78
RegionalComputedLane ::=  Reg-ComputedLane
 
-- =============================================================================
-- DF_Regional_ConnectionManeuverAssist (Desc Name) Record 79
RegionalConnectionManeuverAssist ::=  Reg-ConnectionManeuverAssist
 
-- =============================================================================
-- DF_Regional_GenericLane (Desc Name) Record 80
RegionalGenericLane ::=  Reg-GenericLane
 
-- =============================================================================
-- DF_Regional_Intersection (Desc Name) Record 81
RegionalIntersection ::=  Reg-Intersection
 
-- =============================================================================
-- DF_Regional_IntersectionState (Desc Name) Record 82
RegionalIntersectionState ::=  Reg-IntersectionState
 
-- =============================================================================
-- DF_Regional_RegionalLaneAttributes (Desc Name) Record 83
RegionalLaneAttributes ::=  Reg-LaneAttributes
 
-- =============================================================================
-- DF_Regional_LaneDataAttribute (Desc Name) Record 84
RegionalLaneDataAttribute ::=  Reg-LaneDataAttribute
 
-- =============================================================================
-- DF_Regional_MapData (Desc Name) Record 85
RegionalMapData ::=  Reg-MapData
 
-- =============================================================================
-- DF_Regional_MovementEvent (Desc Name) Record 86
RegionalMovementEvent ::=  Reg-MovementEvent
 
-- =============================================================================
-- DF_Regional_MovementState (Desc Name) Record 87
RegionalMovementState ::=  Reg-MovementState
 
-- =============================================================================
-- DF_Regional_RegionalNodeAttribute (Desc Name) Record 88
RegionalNodeAttribute ::=  Reg-NodeAttribute
 
-- =============================================================================
-- DF_RegionalNodeAttributeList (Desc Name) Record 89
RegionalNodeAttributeList ::=  SEQUENCE (SIZE(1..8)) OF RegionalNodeAttribute
 
-- =============================================================================
-- DF_Regional_NodeOffsetPoint (Desc Name) Record 90
RegionalNodeOffsetPoint ::=  Reg-NodeOffsetPoint
 
-- =============================================================================
-- DF_Regional_Position3D (Desc Name) Record 91
RegionalPosition3D ::=  Reg-Position3D

-- =============================================================================
-- DF_Regional_RestrictionUserType (Desc Name) Record 92
RegionalRestrictionUserType ::=  Reg-RestrictionUserType
 
-- =============================================================================
-- DF_Regional_RoadSegment (Desc Name) Record 93
RegionalRoadSegment ::=  Reg-RoadSegment
 
-- =============================================================================
-- DF_Regional_SignalControlZone (Desc Name) Record 94
RegionalSignalControlZone ::=  Reg-SignalControlZone
 
-- =============================================================================
-- DF_Regional_SPAT (Desc Name) Record 95
RegionalSPAT ::=  Reg-SPAT
 
-- =============================================================================
-- DF_RegulatorySpeedLimit (Desc Name) Record 99
RegulatorySpeedLimit ::=  SEQUENCE {
   type        SpeedLimitType, 
               -- The type of regulatory speed which follows.
			   
   speed       Velocity
               -- The speed in units of 0.02 m/s
               -- when expressed in MPH this shall be rounded
               -- to the closest integer value
               -- See Remarks under the SpeedAdvice entry for
               -- converting and transmitting a speed expressed
               -- in MPH to units of 0.1 m/s
   }
 
-- =============================================================================
-- DF_RestrictionClassAssignment (Desc Name) Record 100
RestrictionClassAssignment ::=  SEQUENCE {
   id       RestrictionClassID,
            -- the unique value (within an intersection or local region)
            -- that is assigned to this group of users.
			
   users    RestrictionUserTypeList 
            -- The list of user types/classes 
            -- to which this restriction ID applies
   }
 
-- =============================================================================
-- DF_RestrictionClassList (Desc Name) Record 101
RestrictionClassList ::=  SEQUENCE (SIZE(1..254)) OF
   RestrictionClassAssignment
 
-- =============================================================================
-- DF_RestrictionUserType (Desc Name) Record 102
RestrictionUserType ::=  CHOICE {
   basicType   RestrictionAppliesTo,
               -- a set of the most commonly used types.
			   
   regional    RegionalRestrictionUserType 
               -- regional extensions
   }
 
-- =============================================================================
-- DF_RestrictionUserTypeList (Desc Name) Record 103
RestrictionUserTypeList ::=  SEQUENCE (SIZE(1..16)) OF  RestrictionUserType
 
-- =============================================================================
-- DF_RoadLaneSetList (Desc Name) Record 104
RoadLaneSetList ::=  SEQUENCE (SIZE(1..255)) OF GenericLane
 
-- =============================================================================
-- DF_RoadSegment CHANGED (Desc Name) Record 105
RoadSegment ::=  SEQUENCE {
   name        DescriptiveName OPTIONAL,
   
   id          RoadSegmentReferenceID,
                           -- a globally unique value for the segment
   
   revision    MsgCount,    
				-- Required default values about the descriptions to follow.
				
   refPoint    Position3D-2, -- the reference from which subsequent
                           -- data points are offset until a new
                           -- point is used.
						   
   laneWidth   LaneWidth OPTIONAL,   
                            -- Reference width used by all subsequent 
                            -- lanes unless a new width is given.
							
   speedLimits SpeedLimitList OPTIONAL, 
                            -- Reference regulatory speed limits
                            -- used by all subsequent 
                            -- lanes unless a new speed is given   
                            -- See Remarks under the SpeedAdvice entry 
                            -- for converting and transmitting a speed 
                            -- expressed in MPH to units of 0.1 m/s
				-- Data describing disruptions in the RoadSegment
				-- such as work zones etc will be added here;
				-- The details regarding each lane type in the RoadSegment.
   
   roadLaneSet RoadLaneSetList,   
   
   regional     RegionalRoadSegment OPTIONAL, 
                           -- regional extensions
   ...
   }
 

-- =============================================================================
-- DF_RoadSegmentList (Desc Name) Record 106
RoadSegmentList ::=  SEQUENCE (SIZE(1..32)) OF RoadSegment

 
-- =============================================================================
-- DF_RoadSegmentReferenceID (Desc Name) Record 107
RoadSegmentReferenceID ::=  SEQUENCE {
   region  RoadRegulatorID OPTIONAL,
           -- a globally unique regional assignment value
           -- typical assigned to a regional DOT authority
           -- the value zero shall be used for testing needs
		   
   id      RoadSegmentID
           -- a unique mapping to the road segment
           -- in question within the above region of use
           -- during its period of aggiment and use
           -- note that unlike intserectionID values, 
           -- this value can be reused by the region
   }
 

-- =============================================================================
-- DF_SegmentAttributeList (Desc Name) Record 113
SegmentAttributeList ::=  SEQUENCE (SIZE(1..8)) OF SegmentAttribute
 

-- =============================================================================
-- DF_SpeedLimitList (Desc Name) Record 122
SpeedLimitList ::=  SEQUENCE (SIZE(1..9)) OF RegulatorySpeedLimit
 
-- =============================================================================
-- DF_TimeChangeDetails CHANGED (Desc Name) Record 123
TimeChangeDetails ::=  SEQUENCE {
   startTime   TimeMark           OPTIONAL,
               -- When this phase 1st started
			   
   minEndTime  TimeMark,
               -- Expected shortest end time
			   
   maxEndTime  TimeMark           OPTIONAL,
               -- Expected longer end time
   
   likelyTime  TimeMark           OPTIONAL,
               -- Best predicted value based on other data              
   confidence  TimeIntervalConfidence OPTIONAL,
               -- Applies to above time element only
   
   nextTime    TimeMark           OPTIONAL
               -- A rough estimate of time when 
               -- this phase may next occur again
               -- used to support various ECO driving power 
               -- management needs.
   }
 
-- -_-_-_-_-_-_-_-_-_-_-_-_-_-_-_-_-_-_-_-_-_-_-_-_-_-_-_-_
-- 
-- Start of entries from table Data_Elements...
-- This table typicaly contains data element entries.
-- -_-_-_-_-_-_-_-_-_-_-_-_-_-_-_-_-_-_-_-_-_-_-_-_-_-_-_-_
 
-- =============================================================================
-- DE_AdvisorySpeedType (Desc Name) Record 3
AdvisorySpeedType ::= ENUMERATED {
    none,
    greenwave,
    ecoDrive,
    transit,
    ...  
    }
 
-- =============================================================================
-- DE_AllowedManeuvers (Desc Name) Record 4
-- Region D: Not used e.g. in Europe
-- The information within "maneuver" is not precise
-- Use "connectsTo" for maneuver description
AllowedManeuvers ::= BIT STRING {
    -- With bits as defined:
    -- Allowed and maneuvers at path end (stop line)
    -- All maneuvers with bits not set are therefore prohibited !
    -- A value of zero shall be used for unknown, indicating no Maneuver
	
    maneuverStraightAllowed      (0), 
                                  -- a Straight movement is allowed in this lane
    maneuverLeftAllowed          (1),  
                                 -- a Left Turn movement is allowed in this lane
    maneuverRightAllowed         (2), 
                                 -- a Right Turn movement is allowed in this lane
    maneuverUTurnAllowed         (3), 
                                 -- a U turn movement is allowed in this lane
    maneuverLeftTurnOnRedAllowed (4), 
                                 -- a Stop, and then proceed when safe movement 
                                 -- is allowed in this lane  
    maneuverRightTurnOnRedAllowed (5), 
                                 -- a Stop, and then proceed when safe movement 
                                 -- is allowed in this lane  
    maneuverLaneChangeAllowed    (6), 
                                 -- a movement which changes to an outer lane 
                                 -- on the egress side is allowed in this lane
                                 -- (example: left into either outbound lane)
    maneuverNoStoppingAllowed    (7), 
                                 -- the vehicle should not stop at the stop line
                                 -- (example: a flashing green arrow)
    yieldAllwaysRequired         (8), 
                                 -- the allowed movements above are not protected 
                                 -- (example: an permanent yellow condition)
    goWithHalt                   (9), 
                                 -- after making a full stop, may proceed
    caution                      (10), 
                                 -- proceed past stop line with caution
    reserved1                    (11)
                                 -- used to align to 12 Bit Field
   
   } (SIZE(12))

   
-- =============================================================================
-- DE_Angle (Desc Name) Record 7
Angle ::= INTEGER (0..28800) 
   -- LSB of 0.0125 degrees
   -- A range of 0 to 359.9875 degrees

   
-- =============================================================================
-- DE_ApproachID (Desc Name) Record 9
ApproachID ::= INTEGER (0..15) -- zero to be used when valid value is unknown

 
-- =============================================================================
-- DE_DeltaAngle (Desc Name) Record 23
DeltaAngle ::= INTEGER (-150..150) 
   -- With an angle range from 
   -- negative 150 to positive 150 
   -- in one degree steps where zero is directly
   -- along the lane center line as defined by the
   -- two closest points

   
-- =============================================================================
-- DE_DescriptiveName (Desc Name) Record 24
DescriptiveName ::= IA5String (SIZE(1..63))

 
-- =============================================================================
-- DE_DrivenLineOffsetLarge (Desc Name) Record 34
DrivenLineOffsetLg ::= INTEGER (-32767..32767) 
   -- LSB units are 1 cm.

   
-- =============================================================================
-- DE_DrivenLineOffsetSmall (Desc Name) Record 35
DrivenLineOffsetSm ::= INTEGER (-2047..2047) 
   -- LSB units are 1 cm.

   
-- =============================================================================
-- DE_DSecond2 CHANGED (Desc Name) Record 38
DSecond2 ::= INTEGER (0..65535) -- units of miliseconds

 
-- =============================================================================
-- DE_DSRC_MessageID2 CHANGED (Desc Name) Record 40
DSRCmsgID2 ::= INTEGER (0..255)
   -- UPER forms
   mapData-P                         DSRCmsgID2 ::= 18 --'12'H MAP,
   signalPhaseAndTimingMessage-P     DSRCmsgID2 ::= 19 --'13'H SPAT
                     -- values to 127 reserved for std use
                     -- values 128 to 255 reserved for local use

					 
-- =============================================================================
-- DE_DSRC_MessageSubID (Desc Name) Record 41
DSRCmsgSubID ::= INTEGER (0..255) -- to be set to zero when used at this time

 
-- =============================================================================
-- DE_Elevation2 CHANGED (Desc Name) Record 44
Elevation2 ::= INTEGER (-4096..61439) 
    -- In units of 10 cm steps above or below the reference ellipsoid
    -- Providing a range of -409.5 to + 6143.9 meters
    -- The value -4096 shall be used when Unknown is to be sent

	
-- =============================================================================
-- DE_IntersectionID CHANGED (Desc Name) Record 55
IntersectionID ::= INTEGER (0..65535)
   -- The values zero through 255 are allocated for testing purposes
   -- Note that the value assign to an intersection will be
   -- unique within a given regional ID only

   
-- =============================================================================
-- DE_IntersectionStatusObject CHANGED (Desc Name) Record 56
IntersectionStatusObject ::= BIT STRING {
    manualControlIsEnabled                (0),
      -- Timing reported is per programmed values, etc but person
      -- at cabinet can manually request that certain intervals are
      -- terminated early (e.g. green).
	  
    stopTimeIsActivated                   (1),
      -- And all counting/timing has stopped.
	  
    failureFlash                          (2), 
      -- Above to be used for any detected hardware failures, 
      -- e.g. conflict monitor as well as for police flash 
	  
    preemptIsActive                       (3),
	
    transitSignalPriorityIsActive         (4),   
      -- Refered to as TSP
	 
    -- Additional states
    fixedTimeOperation                    (5),
      -- Schedule of signals is based on time only 
      -- (i.e. the state can be calculated)
	  
    trafficDependentOperation             (6),
      -- Operation is based on different levels of traffic parameters 
      -- (requests, duration of gaps or more complex parameters)
	  
    standbyOperation                      (7),
      -- Controller: partially switched off or partially amber flashing
	  
    failureMode                           (8),
      -- Controller has a problem or failure in operation
	  
    off                                   (9),
      -- Controller is switched off
	 
    -- Related to MAP an SPAT bindings
    recentMAPmessageUpdate                (10),
      -- Map revision with content changes
	  
    recentChangeInMAPassignedLanesIDsUsed (11),
      -- Change in MAP's assigned lanes used (lane changes)
      -- Changes in the active lane list description
	  
    noValidMAPisAvailableAtThisTime       (12),
      -- MAP (and vaious lanes indexes) not available
	  
    noValidSPATisAvailableAtThisTime      (13)
      -- SPAT system is not working at this time
    
    -- Bit values (14,15) reserved at ths time and shall be zero
    } (SIZE(16))

	
-- =============================================================================
-- DE_LaneAttributes-Barrier (Desc Name) Record 57
LaneAttributes-Barrier ::= BIT STRING {
   -- With bits as defined:
   median-RevocableLane     (0),
                            -- this lane may be activated or not based
                            -- on the current SPAT message contents
                            -- if not asserted, the lane is ALWAYS present
							
   median                   (1),
   whiteLineHashing         (2),
   stripedLines             (3),
   doubleStripedLines       (4),
   trafficCones             (5),
   constructionBarrier      (6),
   trafficChannels          (7),
   lowCurbs                 (8),
   highCurbs                (9)
   -- Bits 10~15 reserved and set to zero
   } (SIZE (16))

   
-- =============================================================================
-- DE_LaneAttributes-Bike CHANGED (Desc Name) Record 58
LaneAttributes-Bike ::= BIT STRING {
   -- With bits as defined:
   bikeRevocableLane       (0),
                           -- this lane may be activated or not based
                           -- on the current SPAT message contents
                           -- if not asserted, the lane is ALWAYS present
						   
   pedestrianUseAllowed    (1),
                           -- The path allows pedestrian traffic, 
                           -- if not set, this mode is prohibited
						   
   isBikeFlyOverLane       (2),
                           -- path of lane is not at grade
						   
   fixedCycleTime          (3),
                           -- the phases use preset times
                           -- i.e. there is not a 'push to cross' button
						   
   biDirectionalCycleTimes (4),
                           -- ped walk phases use different SignalGroupID
                           -- for each direction. The first SignalGroupID
                           -- in the first Connection represents 'inbound'
                           -- flow (the direction of travel towards the first 
                           -- node point) while second SignalGroupID in the 
                           -- next Connection entry represents the 'outbound'
                           -- flow. And use of RestrictionClassID entires
                           -- in the Connect follow this same pattern in pairs.
						   
   isolatedByBarrier       (5),
   
   unsignalizedSegmentsPresent  (6)
                           -- The lane path consists of one of more segments
                           -- which are not part of a signal group ID

   -- Bits 7~15 reserved and set to zero
   } (SIZE (16))

   
-- =============================================================================
-- DE_LaneAttributes-Crosswalk CHANGED (Desc Name) Record 59
LaneAttributes-Crosswalk ::= BIT STRING { 
   -- With bits as defined:
   -- MUTCD provides no suitable "types" to use here
   crosswalkRevocableLane  (0),
                           -- this lane may be activated or not based
                           -- on the current SPAT message contents
                           -- if not asserted, the lane is ALWAYS present
						   
   bicyleUseAllowed        (1),
                           -- The path allows bicycle traffic, 
                           -- if not set, this mode is prohibited
						   
   isXwalkFlyOverLane      (2),
                           -- path of lane is not at grade
						   
   fixedCycleTime          (3),
                           -- ped walk phases use preset times
                           -- i.e. there is not a 'push to cross' button
						   
   biDirectionalCycleTimes (4),
                           -- ped walk phases use different SignalGroupID
                           -- for each direction. The first SignalGroupID
                           -- in the first Connection represents 'inbound'
                           -- flow (the direction of travel towards the first 
                           -- node point) while second SignalGroupID in the 
                           -- next Connection entry represents the 'outbound'
                           -- flow. And use of RestrictionClassID entires
                           -- in the Connect follow this same pattern in pairs.
						   
   hasPushToWalkButton     (5),
                           -- Has a demand input
						   
   audioSupport            (6),
                           -- audio crossing cues present
						   
   rfSignalRequestPresent  (7),
                           -- Supports RF push to walk technologies
						   
   unsignalizedSegmentsPresent  (8)
                           -- The lane path consists of one of more segments
                           -- which are not part of a signal group ID
						   
   -- Bits 9~15 reserved and set to zero
   } (SIZE (16))

   
-- =============================================================================
-- DE_LaneAttributes-ParkingLane (Desc Name) Record 60
LaneAttributes-Parking ::= BIT STRING { 
    -- With bits as defined:
    -- Parking use details, note that detailed restrictions such as 
    -- allowed hours are sent by way of ITIS codes in the TIM message
	
    parkingRevocableLane         (0),
                                 -- this lane may be activated or not based
                                 -- on the current SPAT message contents
                                 -- if not asserted, the lane is ALWAYS present
								 
    parallelParkingInUse         (1),
	
    headInParkingInUse           (2),
	
    doNotParkZone                (3),
                                 -- used to denote fire hydrants as well
                                 -- short disruptions in a parking zone
								 
    parkingForBusUse             (4),
    parkingForTaxiUse            (5),
    noPublicParkingUse           (6)
                                 -- private parking, as in front of
                                 -- private property
								 
   -- Bits 7~15 reserved and set to zero
   } (SIZE (16))

   
-- =============================================================================
-- DE_LaneAttributes-Sidewalk (Desc Name) Record 61
LaneAttributes-Sidewalk ::= BIT STRING { 
   -- With bits as defined:
   sidewalk-RevocableLane  (0),
                           -- this lane may be activated or not based
                           -- on the current SPAT message contents
                           -- if not asserted, the lane is ALWAYS present.
						   
   bicyleUseAllowed        (1),
                           -- The path allows bicycle traffic, 
                           -- if not set, this mode is prohibited.
						   
   isSidewalkFlyOverLane   (2),
                           -- path of lane is not at grade.
						   
   walkBikes               (3)
                           -- bike traffic must dismount and walk.
						   
   -- Bits 4~15 reserved and set to zero
   } (SIZE (16))

   
-- =============================================================================
-- DE_LaneAttributes-Striping (Desc Name) Record 62
LaneAttributes-Striping ::= BIT STRING { 
   -- With bits as defined:
    stripToConnectingLanesRevocableLane (0),
       -- this lane may be activated or not based
       -- on the current SPAT message contents
       -- if not asserted, the lane is ALWAYS present.
	   
    stripDrawOnLeft                (1),
	
    stripDrawOnRight               (2),
        -- which side of lane to mark.
		
    stripToConnectingLanesLeft     (3),
	
    stripToConnectingLanesRight    (4),
	
    stripToConnectingLanesAhead    (5)
        -- the stripe type should be
        -- presented to the user visually
        -- to reflect stripes in the 
        -- intersection for the type of
        -- movement indicated
		
   -- Bits 6~15 reserved and set to zero
   } (SIZE (16))

   
-- =============================================================================
-- DE_LaneAttributes-TrackedVehicle (Desc Name) Record 63
LaneAttributes-TrackedVehicle ::= BIT STRING { 
   -- With bits as defined:
    spec-RevocableLane         (0),
                               -- this lane may be activated or not based
                               -- on the current SPAT message contents
                               -- if not asserted, the lane is ALWAYS present
							   
    spec-commuterRailRoadTrack (1), 
	
    spec-lightRailRoadTrack    (2),
	
    spec-heavyRailRoadTrack    (3),
	
    spec-otherRailType         (4)
	
   -- Bits 5~15 reserved and set to zero
   } (SIZE (16))

   
-- =============================================================================
-- DE_LaneAttributes-Vehicle (Desc Name) Record 64
LaneAttributes-Vehicle ::= BIT STRING {  
    -- With bits as defined:
    isVehicleRevocableLane       (0),
                                 -- this lane may be activated or not based
                                 -- on the current SPAT message contents
                                 -- if not asserted, the lane is ALWAYS present
								 
    isVehicleFlyOverLane         (1),
                                 -- path of lane is not at grade
								 
    hovLaneUseOnly               (2),
	
    restrictedToBusUse           (3),
	
    restrictedToTaxiUse          (4),
	
    restrictedFromPublicUse      (5),
	
    hasIRbeaconCoverage          (6)

   -- Bits 7~15 reserved and set to zero
   } (SIZE (16))

   
-- =============================================================================
-- DE_LaneConnectionID (Desc Name) Record 65
LaneConnectionID ::= INTEGER (0..255)

 
-- =============================================================================
-- DE_LaneDirection (Desc Name) Record 66
LaneDirection ::= BIT STRING {
    -- With bits as defined:
    -- Allowed directions of travel in the lane object
    -- All lanes are described from the stop line outwards
    ingressPath                 (0), 
                                -- travel from rear of path to front 
                                -- is allowed
								
    egressPath                  (1)
                                -- travel from front of path to rear 
                                -- is allowed
								
    -- Notes:  No Travel, i.e. the lane object type does not support
    --         travel (medians, curbs, etc.) is indicated by not 
    --         asserting any bit value
    --         Bi-Directional Travel (such as a ped crosswalk) is 
    --         indicated by asserting both of the bits
    } (SIZE (2))

	
-- =============================================================================
-- DE_LaneId CHANGED (Desc Name) Record 67
LaneID ::= INTEGER (0..255)
   -- the value 0 shall be used when the lane ID is
   -- not available or not known
   -- the value 255 is reserved for future use

   
-- =============================================================================
-- DE_LaneSharing (Desc Name) Record 69
LaneSharing ::= BIT STRING {
    -- With bits as defined:
	
    overlappingLaneDescriptionProvided  (0),
    -- Assert when another lane object is present to describe the
    -- path of the overlapping shared lane
    -- this construct is not used for lane objects which simply cross.
	
    multipleLanesTreatedAsOneLane       (1),
    -- Assert if the lane object path and width details represents
    -- multiple lanes within it that are not further described

    -- Various modes and type of traffic whhc may share this lane:
    otherNonMotorizedTrafficTypes       (2), -- horse drawn etc.
    individualMotorizedVehicleTraffic   (3),
    busVehicleTraffic                   (4),  
    taxiVehicleTraffic                  (5),
    pedestriansTraffic                  (6),
    cyclistVehicleTraffic               (7),
    trackedVehicleTraffic               (8),
    pedestrianTraffic                   (9)
    } (SIZE (10))
    -- All zeros would indicate 'not shared' and 'not overlapping'

	
-- =============================================================================
-- DE_LaneWidth (Desc Name) Record 70
LaneWidth ::= INTEGER (0..32767) -- units of 1 cm

 
-- =============================================================================
-- DE_LayerID (Desc Name) Record 72
LayerID ::= INTEGER (0..100)


-- =============================================================================
-- DE_LayerType (Desc Name) Record 73
LayerType ::= ENUMERATED {
     none, 
     mixedContent, -- two or more of the below types
     generalMapData, 
     intersectionData, 
     curveData, 
     roadwaySectionData, 
     parkingAreaData, 
     sharedLaneData,
     ... 
     }

	 
-- =============================================================================
-- DE_MergeDivergeNodeAngle (Desc Name) Record 78
MergeDivergeNodeAngle ::= INTEGER (-180..180) 
   -- In units of 1.5 degrees for north
   -- the value -180 shall be used to represent 
   -- data is not available or unknown

   
-- =============================================================================
-- DE_MinuteOfTheYear (Desc Name) Record 79
MinuteOfTheYear ::= INTEGER (0..527040) 
   -- the value 527040 shall be used for invalid

   
-- =============================================================================
-- DE_MovementPhaseState CHANGED (Desc Name) Record 81
MovementPhaseState ::= ENUMERATED {
    -- Note that based on the regions and the operating mode not every 
    -- phase will be used in all transportation modes and that not 
    -- every phase will be used in all transportation modes
  
    unavailable (0), 
      -- This state is used for unknown or error.
	  
    dark (1),   
      -- The signal head is dark (unlit).
	  

   -- Reds
    stop-Then-Proceed (2), 
      -- Often called 'flashing red' in US
      -- Driver Action:                     
      --   Stop vehicle at stop line. 
      --   Do not proceed unless it is safe.
      -- Note that the right to proceed either right or left when 
      -- it is safe may be contained in the lane description to 
      -- handle what is called a 'right on red'.
	  
    stop-And-Remain (3),
      -- e.g. called 'red light' in US
      -- Driver Action:                     
      --   Stop vehicle at stop line. 
      --   Do not proceed.                     
      -- Note that the right to proceed either right or left when 
      -- it is safe may be contained in the lane description to 
      -- handle what is called a 'right on red'.
	  
   
   -- Greens
    pre-Movement (4), 
      -- Not used in the US, red+yellow partly in REG-D (e.g. Europe(
      -- Driver Action:                     
      --   Stop vehicle. 
      --   Prepare to proceed (pending green)
      --   (Prepare for transition to green/go).
	  
    permissive-Movement-Allowed (5), 
      -- Often called 'permissive green' in US
      -- Driver Action:                     
      --   Proceed with caution, 
      --   must yield to all conflicting traffic 
      -- Conflicting traffic may be present
      -- in the intersection conflict area.
	  
    protected-Movement-Allowed (6), 
      -- Often called 'protected green' in US
      -- Driver Action:                     
      --   Proceed, tossing caution to the wind, 
      --   in indicated (allowed) direction.
   
   -- Yellows / Ambers
   -- The vehicle is not allowed to cross the stop bar if it is possible 
   -- to stop without danger. 
    permissive-clearance (7), 
      -- Often called 'permissive yellow' in US
      -- Driver Action:                     
      --   Prepare to stop.
      --   Proceed if unable to stop,
      --   Clear Intersection.
      -- Conflicting traffic may be present
      -- in the intersection conflict area.
	  
    protected-clearance (8),  
      -- Often called 'protected yellow' in US
      -- Driver Action: 
      --   Prepare to stop.
      --   Proceed if unable to stop,
      --   in indicated direction (to connected lane)
      --   Clear Intersection.
                    
    caution-Conflicting-Traffic (9)
      -- Often called 'flashing yellow' in US
      -- Often used for extended periods of time
      -- Driver Action: 
      --   Proceed with caution, 
      -- Conflicting traffic may be present
      -- in the intersection conflict area
    }
    -- The above number assignments are not used with UPER encoding
    -- and are only to be used with DER or implicit encoding

	
-- =============================================================================
-- DE_MsgCount (Desc Name) Record 82
MsgCount ::= INTEGER (0..127)

 
-- =============================================================================
-- DE_MsgCRC (Desc Name) Record 83
MsgCRC ::= OCTET STRING (SIZE(2)) -- created with the CRC-CCITT polynomial

 
-- =============================================================================
-- DE_NodeAttribute CHANGED (Desc Name) Record 89
NodeAttribute ::= ENUMERATED {
   -- Various values which pertain only to the current node point
   
   -- General Items
   reserved,  
   stopLine,             -- point where a mid-path stop line exists
                         -- See also 'do not block' for segments

   -- Path finish details 
   roundedCapStyleA,      -- Used to control final path rounded end shape
                          -- with edge of curve at final point in a circle.
						  
   roundedCapStyleB,      -- Used to control final path rounded end shape
                          -- with edge of curve extending 50% of width past
                          -- final point in a circle
   
   -- Topography Points (items with no concept of a distance along the path)
   mergePoint,           -- Japan merge with 1 or more lanes
   
   divergePoint,         -- Japan diverge with 1 or more lanes
   
   downstreamStopLine,   -- Japan style downstream intersection 
                                   -- (a 2nd intersection) stop line
								   
   downstreamStartNode,  -- Japan style downstream intersection 
                                   -- (a 2nd intersection) start node
     
   -- Pedestrian Support Attributes
   closedToTraffic,      -- where a pedestrian may NOT go
                         -- to be used during construction events.
						 
   safeIsland,           -- a pedestrian safe stopping point
                         -- also called a traffic island
                         -- This usage described a point feature on a path, 
                         -- other entries can describe a path.
						 
   curbPresentAtStepOff, -- the sidewalk to street curb is NOT 
                         -- angled where it meets the edge of the 
                         -- roadway (user must step up/down)
 
   -- Lane geometry details  (see standard for defined shapes)
   hydrantPresent,       -- Or other services access 
   ...
   }

   
-- =============================================================================
-- DE_Offset_B10 (Desc Name) Record 94
Offset-B10 ::= INTEGER (-512..511)

 
-- =============================================================================
-- DE_Offset_B11 (Desc Name) Record 95
Offset-B11 ::= INTEGER (-1024..1023)

 
-- =============================================================================
-- DE_Offset_B12 (Desc Name) Record 96
Offset-B12 ::= INTEGER (-2048..2047)

 
-- =============================================================================
-- DE_Offset_B13 (Desc Name) Record 97
Offset-B13 ::= INTEGER (-4096..4095)

 
-- =============================================================================
-- DE_Offset_B14 (Desc Name) Record 98
Offset-B14 ::= INTEGER (-8192..8191)

 
-- =============================================================================
-- DE_Offset_B16 (Desc Name) Record 99
Offset-B16 ::= INTEGER (-32768..32767)

 
-- =============================================================================
-- DE_PedestrianBicycleDetect (Desc Name) Record 102
PedestrianBicycleDetect ::= BOOLEAN -- 
                 -- true if ANY Pedestrians or Bicyclists are 
                 -- detected crossing the target lane or lanes

				 
-- =============================================================================
-- DE_PrioritizationResponseStatus (Desc Name) Record 104
PrioritizationResponseStatus ::= ENUMERATED {
   unknown     (0),
               -- unknown state
   requested   (1),
               -- this prioritization request was detected 
               -- by the traffic controller.
			   
   processing  (2),
               -- checking request 
               -- (request is in queue, others requests are prior).
			   
   watchOtherTraffic (3),
               -- can not give full permission, 
               -- therefore watch for other traffic.
			   
   granted     (4),
               -- intervention was successful 
               -- and now prioritization is active.
			   
   rejected    (5),
               -- the prioritization or preemption request was 
               -- rejected by the traffic controller.
			   
   maxPresence (6)
               -- request has exceeded maxPresence time
   }

-- =============================================================================
-- DE_RestrictionAppliesTo  CHANGED (Desc Name) Record 110
RestrictionAppliesTo ::= ENUMERATED {
    none,              -- applies to nothing
    equippedTransit,   -- buses etc.
    equippedTaxis,
	
    equippedOther,     -- other vehicle types with
                       -- necessary signal phase state
                       -- reception equipment.
					   
    emissionCompliant, -- regional variants with more
                       -- definitive items also exist
    equippedBicycle,
    weightCompliant,
    heightCompliant,
                       -- Items dealing with traveler needs
                       -- (presumed to be suitably equipped).
	
    pedestrians,
    slowMovingPersons,
    wheelchairUsers,
    visualDisabilities,
    audioDisabilities,  -- hearing
    otherUnknownDisabilities,
    ...
    }

	
-- =============================================================================
-- DE_RestrictionClassID (Desc Name) Record 111
RestrictionClassID ::= INTEGER (0..255)
   -- An index value to identify data about classes of users
   -- the value used varies with each intersection's
   -- needs and is defined in the map to the assigned 
   -- classes of supported users.

   
-- =============================================================================
-- DE_RoadRegulatorID CHANGED (Desc Name) Record 112
RoadRegulatorID ::= INTEGER (0..65535)
   -- The value zero shall be used for testing only

   
-- =============================================================================
-- DE_RoadSegmentID (Desc Name) Record 113
RoadSegmentID ::= INTEGER (0..65535)
   -- The values zero to 255 shall be used for testing only
   -- Note that the value assign to an RoadSegment will be
   -- unique within a given regional ID only during its use

   
-- =============================================================================
-- DE_RoadwayCrownAngle (Desc Name) Record 114
RoadwayCrownAngle ::= INTEGER (-128..127) 
    -- In LSB units of 0.3 degrees of angle
    -- over a range of -38.1 to + 38.1 degrees
    -- The value -128 shall be used for unknown
    -- The value zero shall be used for angles 
    -- which are between -0.15 and +0.15

	
-- =============================================================================
-- DE_Scale_B12 (Desc Name) Record 118
Scale-B12 ::= INTEGER (-2048..2047)  -- in steps of 0.05 percent

 
-- =============================================================================
-- DE_SegmentAttribute (Desc Name) Record 119
SegmentAttribute ::= ENUMERATED {
   -- Various values which can be Enabled and Disabled for a lane segement
   
   -- General Items
   reserved                  ,  
   doNotBlock                ,  -- segment where a vehicle 
                                -- may not come to a stop.
								
   whiteLine                 ,  -- segment where lane crossing not allowed
                                -- such as the final few meters of a lane.
   
   -- Porous Lane states, merging, turn outs, parking etc.
   
   mergingLaneLeft           ,  -- indicates porous lanes
   mergingLaneRight          ,
   
   curbOnLeft                ,  -- indicates presence of curbs
   curbOnRight               ,
   
   loadingzoneOnLeft         ,  -- loading or drop off zones
   loadingzoneOnRight        ,
   
   turnOutPointOnLeft        ,  -- opening to adjacent street/alley/road
   turnOutPointOnRight       ,
   
   adjacentParkingOnLeft     , -- side of road parking
   adjacentParkingOnRight    ,
   
   -- Bike Lane Needs
   adjacentBikeLaneOnLeft    , -- presence of marked bike lanes
   adjacentBikeLaneOnRight   ,
   sharedBikeLane            , -- right of way is shared with bikes
                               -- who may occupy entire lane width
   bikeBoxInFront            ,
   
   -- Transit Needs
   transitStopOnLeft         , -- any form of bus/transit loading
                               -- with pull in-out access to lane on left.
							   
   transitStopOnRight        , -- any form of bus/transit loading
                               -- with pull in-out access to lane on right.
							   
   transitStopInLane         , -- any form of bus/transit loading
                               -- in mid path of the lane.
							   
   sharedWithTrackedVehicle  , -- lane is shared with train or trolley 
                               -- not used for crossing tracks
  
     
   -- Pedestrian Support Attributes
   safeIsland                , -- begin/end a safety island in path
   lowCurbsPresent           , -- for ADA support
   rumbleStripPresent        , -- for ADA support
   audibleSignalingPresent   , -- for ADA support
   adaptiveTimingPresent     , -- for ADA support
   rfSignalRequestPresent    , -- Supports RF push to walk technologies
   
   partialCurbIntrusion      , -- path is blocked by a median or curb 
                               -- but at least 1 meter remains open for use
                               -- and at-grade passage
   
   -- Lane geometry details  (see standard for defined shapes)
   taperToLeft               , -- Used to control final path shape
   taperToRight              , -- Used to control final path shape
   taperToCenterLine         , -- Used to control final path shape

   -- Parking Lane and Curb Attributes
   parallelParking           , -- 
   headInParking             , -- Parking at an angle with the street
   freeParking               , -- no restriction on use of parking.
   
   timeRestrictionsOnParking , -- Parking is not permitted at all times
                               -- typically used when the 'parking' lane 
                               -- becomes a driving lane at times.
							   
   costToPark                , -- Used parking has a cost
   midBlockCurbPresent       , -- a protruding curb near lane edge
   unEvenPavementPresent     , -- a disjoint height at lane edge
   ...
   }

   
-- =============================================================================
-- DE_SignalControlState (Desc Name) Record 120
SignalControlState ::= OCTET STRING (SIZE(1)) 
    -- With bits set as follows:
   
    -- Bit 7 (MSB) Set if the state is currently active
    -- only one active state can exist at a time, and 
    -- this state should be sent first in any sequences
   
    -- Bits 6~4 The preempt or priority value that is 
    -- being described.  
   
    -- Bits 3~0 the state bits, indicating either a 
    -- preemption or a priority use as follows: 
   
    -- If a preemption: to follow the 
    -- preemptState object of NTCIP 1202 v2.19f  
    -- See PreemptState for bit definitions.
   
    -- If a prioirty to follow the 
    -- tspInputStatus object utilized in the 
    -- NYC ASTC2 traffic controller
    -- See PriorityState for bit definitions

	
-- =============================================================================
-- DE_SignalGroupID (Desc Name) Record 121
SignalGroupID ::= INTEGER (0..255) 
    -- The value 0 shall be used when the ID is
    -- not available or not known
    -- the value 255 is reserved to indicate a 
    -- permanent green movement state
    -- therefore a simple 8 phase signal controller 
    -- device might use 1..9 as its groupIDs

	
-- =============================================================================
-- DE_SpeedAdvice CHANGED (Desc Name) Record 127
SpeedAdvice ::= INTEGER (0..500) -- Units of 0.1 m/s
         -- The value 500 indicates that 
         -- speed is unavailable

		 
-- =============================================================================
-- DE_SpeedLimitType (Desc Name) Record 129
SpeedLimitType ::= ENUMERATED {
    unknown,                    -- Speed limit type not available
    maxSpeedInSchoolZone,       -- Only sent when the limit is active
    maxSpeedInSchoolZoneWhenChildrenArePresent, -- Sent at any time
    maxSpeedInConstructionZone, -- Used for work zones, incident zones, etc.
                                -- where a reduced speed is present
    vehicleMinSpeed,
    vehicleMaxSpeed,            -- Regulatory speed limit for general traffic
    vehicleNightMaxSpeed,

    truckMinSpeed,
    truckMaxSpeed,
    truckNightMaxSpeed,

    vehiclesWithTrailersMinSpeed,
    vehiclesWithTrailersMaxSpeed,
    vehiclesWithTrailersNightMaxSpeed,
    ...
    }

	
-- =============================================================================
-- DE_TimeIntervalConfidence (Desc Name) Record 144
TimeIntervalConfidence ::= INTEGER (0..15)   
   -- Value   Probability
   --   0         21%
   --   1         36%
   --   2         47%
   --   3         56%
   --   4         62%
   --   5         68%
   --   6         73%
   --   7         77%
   --   8         81%
   --   9         85%
   --   10        88%
   --   11        91%
   --   12        94%
   --   13        96%
   --   14        98%
   --   15        100%

   
-- =============================================================================
-- DE_TimeMark (Desc Name) Record 145
TimeMark ::= INTEGER (0..36002)
   -- Tenths of a second in the current or next hour
   -- In units of 1/10th second from UTC time
   -- A range of 0~36000 covers one hour
   -- The values 35991..36000 are used when a leap second occurs
   -- The value 36001 is used to indicate time >3600 seconds
   -- 36002 is to be used when value undefined or unknown
   -- Note that this is NOT expressed in GPS time
   -- or in local time

   
-- =============================================================================
-- DE_Velocity CHANGED (Desc Name) Record 169
Velocity ::= INTEGER (0..8191) -- Units of 0.02 m/s
          -- The value 8191 indicates that 
          -- velocity is unavailable

		  
-- =============================================================================
-- DE_WaitOnStopline (Desc Name) Record 173
WaitOnStopline ::= BOOLEAN -- 
         -- True or False
         -- If "true", the vehicles on this specific connecting 
         -- maneuver have to stop on the stop-line
         -- and not to enter the collision area

		 
-- =============================================================================
-- DE_ZoneLength (Desc Name) Record 181
ZoneLength ::= INTEGER (0..10000)
    -- Unit = 1 meter, 0 = unknown, 
    -- The value 10000 to be used for Distances >=10000 m
    -- (e.g. from known point to another point along a 
    -- known path, often against traffic flow direction 
    -- when used for measuring queues)

RegionId ::= INTEGER (0..255)
   noRegion     RegionId ::= 0  -- Use default supplied stubs
   addGrpA      RegionId ::= 1  -- USA
   addGrpB      RegionId ::= 2  -- Japan
   addGrpC      RegionId ::= 3  -- EU
   -- NOTE: new registered regional IDs will be added here
   -- The values 128 and above are for local region use

REG-EXT-ID-AND-TYPE ::= CLASS {
   &id     RegionId UNIQUE,
   &Type
} WITH SYNTAX {&Type IDENTIFIED BY &id}

RegionalExtension {REG-EXT-ID-AND-TYPE : Set} ::= SEQUENCE {
   regionId     REG-EXT-ID-AND-TYPE.&id( {Set} ),
   regExtValue  REG-EXT-ID-AND-TYPE.&Type( {Set}{@regionId} )
}

Reg-NodeOffsetPointXY   REG-EXT-ID-AND-TYPE ::= { ... }

NodeOffsetPointXY ::= CHOICE {
   -- Nodes with X,Y content
   node-XY1         Node-XY-20b,    -- node is within   5.11m of last node
   node-XY2         Node-XY-22b,    -- node is within  10.23m of last node
   node-XY3         Node-XY-24b,    -- node is within  20.47m of last node
   node-XY4         Node-XY-26b,    -- node is within  40.96m of last node
   node-XY5         Node-XY-28b,    -- node is within  81.91m of last node
   node-XY6         Node-XY-32b,    -- node is within 327.67m of last node
   node-LatLon      Node-LLmD-64b,  -- node is a full 32b Lat/Lon range
   regional         RegionalExtension {{Reg-NodeOffsetPointXY}}
                                    -- node which follows is of a regional definition type
}

VehicleHeight ::= INTEGER (0..127)

END 
-- end of the DSRC module.
 
-- ############################################################################
-- ^-^-^-^-^-^-^-^-^-^-^-^-^-^-^-^-^-^-^-^-^-^-^-^-^-^-^-^-^-^-^-^-^-^-^-^-^-^-
-- 
-- Begin module: REGION
-- 
-- ^-^-^-^-^-^-^-^-^-^-^-^-^-^-^-^-^-^-^-^-^-^-^-^-^-^-^-^-^-^-^-^-^-^-^-^-^-^-
-- ############################################################################
REGION DEFINITIONS AUTOMATIC TAGS::= BEGIN 


-- =============================================================================
-- DF_REG_AdvisorySpeed_Base (Desc Name) Record 36
-- From source: AMENDMENT Regional Data J2735 (DSRC)
Reg-AdvisorySpeed ::=  SEQUENCE { ... }


-- =============================================================================
-- DF_REG_ComputedLane_Base (Desc Name) Record 37
-- From source: AMENDMENT Regional Data J2735 (DSRC)
Reg-ComputedLane ::=  SEQUENCE { ... }


-- =============================================================================
-- DF_REG_GenericLane_Base (Desc Name) Record 40
-- From source: AMENDMENT Regional Data J2735 (DSRC)
Reg-GenericLane ::=  SEQUENCE { ... }


-- =============================================================================
-- DF_REG_Intersection_Base (Desc Name) Record 41
-- From source: AMENDMENT Regional Data J2735 (DSRC)
Reg-Intersection ::=  SEQUENCE { ... }


-- =============================================================================
-- DF_REG_LaneAttributes_Base (Desc Name) Record 44
-- From source: AMENDMENT Regional Data J2735 (DSRC)
Reg-LaneAttributes ::=  SEQUENCE { ... }


-- =============================================================================
-- DF_REG_LaneDataAttribute_Base (Desc Name) Record 45
-- From source: AMENDMENT Regional Data J2735 (DSRC)
Reg-LaneDataAttribute ::=  SEQUENCE { ... }


-- =============================================================================
-- DF_REG_MovementEvent_Base (Desc Name) Record 50
-- From source: AMENDMENT Regional Data J2735 (DSRC)
Reg-MovementEvent ::=  SEQUENCE { ... }


-- =============================================================================
-- DF_REG_MovementState_Base (Desc Name) Record 51
-- From source: AMENDMENT Regional Data J2735 (DSRC)
Reg-MovementState ::=  SEQUENCE { ... }


-- =============================================================================
-- DF_REG_NodeAttribute_Base (Desc Name) Record 52
-- From source: AMENDMENT Regional Data J2735 (DSRC)
Reg-NodeAttribute ::=  SEQUENCE { ... }


-- =============================================================================
-- DF_REG_NodeOffsetPoint_Base (Desc Name) Record 53
-- From source: AMENDMENT Regional Data J2735 (DSRC)
Reg-NodeOffsetPoint ::=  SEQUENCE { ... }


-- =============================================================================
-- DF_REG_RoadSegment_Base (Desc Name) Record 60
-- From source: AMENDMENT Regional Data J2735 (DSRC)
Reg-RoadSegment ::=  SEQUENCE { ... }


-- =============================================================================
-- DF_REG_SignalControlZone_Base (Desc Name) Record 61
-- From source: AMENDMENT Regional Data J2735 (DSRC)
Reg-SignalControlZone ::=  SEQUENCE { ... }


-- =============================================================================
-- DF_REG_SPAT_Base (Desc Name) Record 62
-- From source: AMENDMENT Regional Data J2735 (DSRC)
Reg-SPAT ::=  SEQUENCE { ... }


END
-- End of the REGION module.
