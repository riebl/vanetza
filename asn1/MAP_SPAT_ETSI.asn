MAP-SPAT-ETSI DEFINITIONS AUTOMATIC TAGS ::= 

BEGIN

IMPORTS 
   MapData, SPAT FROM DSRC { iso (1) standard (0) signalizedIntersection (19091) profilec(2) dsrc (2) version2 (2) }
   ItsPduHeader FROM ITS-Container { itu-t (0) identified-organization (4) etsi (0) itsDomain (5) wg1 (1) ts (102894) cdd (2) version (2) };

MAPEM ::= SEQUENCE
{
	header	ItsPduHeader,
	mapData	MapData
}

SPATEM ::= SEQUENCE
{
	header	ItsPduHeader,
	spatData SPAT
}

END
