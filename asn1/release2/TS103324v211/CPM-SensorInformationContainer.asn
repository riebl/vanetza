CPM-SensorInformationContainer {itu-t (0) identified-organization (4) etsi (0) itsDomain (5) wg1 (1) ts (103324) sensorInformationContainer (3) major-version-1 (1) minor-version-1(1)}

DEFINITIONS AUTOMATIC TAGS ::=

BEGIN

IMPORTS

Shape, ConfidenceLevel, Identifier1B, SensorType
FROM ETSI-ITS-CDD {itu-t (0) identified-organization (4) etsi (0) itsDomain (5) wg1 (1) ts (102894) cdd (2) major-version-4 (4) minor-version-3 (3) }
;

/**
 * This DF  represents the Sensor Information Container as a list of information objects about the sensors or data fusion systems from which the station provides information about detected objects.
*/
SensorInformationContainer ::= SEQUENCE SIZE(1..128, ...) OF SensorInformation


/**
 * This DF  represents the characteristics of a single sensor or data fusion system.
 *
 * It shall include the following components: 
 *
 * @field sensorId: identifier of the sensor or data fusion system used to relate the perceived object in the Perceived Object Container to the sensor that detected it.
 * this identifier shall uniquely identify the sensor inside the CPM, but may be changed from one CPM to the next.
 *
 * @field sensorType: the type of the sensor.
 *
 * @field perceptionRegionShape: the perception region of the sensor.
 *
 * @field perceptionRegionConfidence: the homogeneous perception region confidence that can be assumed for the entire perception region shape of this sensor. 
 *
 * @field shadowingApplies: indicates if the standard shadowing approach applies to the described perception region.
 *
*/

SensorInformation ::= SEQUENCE {
    sensorId          		    Identifier1B,
    sensorType        		    SensorType,
    perceptionRegionShape		Shape OPTIONAL,
    perceptionRegionConfidence  ConfidenceLevel OPTIONAL,
    shadowingApplies            BOOLEAN,
   ...
}


END
