EtsiTs102941TypesCaManagement
  { itu-t(0) identified-organization(4) etsi(0) itsDomain(5) wg5(5) ts(102941) caManagement(8) major-version-3(3) minor-version-1(1)}

DEFINITIONS AUTOMATIC TAGS ::=
BEGIN

IMPORTS

EtsiTs103097Certificate, EtsiTs103097Data-Signed 
FROM	
EtsiTs103097Module 
{ itu-t(0) identified-organization(4) etsi(0) itsDomain(5) wg5(5) secHeaders(103097) core(1) major-version-3(3) minor-version-1(1) } 
WITH SUCCESSORS

PublicKeys, CertificateSubjectAttributes
FROM EtsiTs102941BaseTypes
{ itu-t(0) identified-organization(4) etsi(0) itsDomain(5) wg5(5) ts(102941) baseTypes(3) major-version-3(3) minor-version-1(1) }
WITH SUCCESSORS
;

/************
-- CA certificate request 
************/

CaCertificateRequest ::= SEQUENCE {
  publicKeys                  PublicKeys,
  requestedSubjectAttributes  CertificateSubjectAttributes,
  ...	 
}

END
